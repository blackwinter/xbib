CIP24-Release-B-APDU DEFINITIONS ::=
BEGIN
IMPORTS IntUnit, InternationalString, Unit FROM Z39-50-APDU-1995
ResourceReport FROM Z39-50-APDU-1995-B;

CIPSpecificInfo ::= CHOICE
{
  searchControl [1] IMPLICIT SearchControl,
  term [2] CIPTerm,
  explainInfo [3] IMPLICIT AdditionalSemanticAttributes,
  childrenResourceReport [4] ChildrenResourceReport
}

SearchControl ::= SEQUENCE
{
  itemDescriptorType [1] IMPLICIT INTEGER
	{
	collectionDescriptorSearch (1),
	productDescriptorSearch (3)
	},
  searchScope [2] IMPLICIT INTEGER
	{
	localSearch (1),
	wideSearch (2)
	}
}

CIPTerm ::= CHOICE
{
  wrsgrs [1] IMPLICIT WRSGRSSpatialCoverage,
  circle [2] IMPLICIT Circle
}

WRSGRSSpatialCoverage ::= SEQUENCE
{
  track [1] IMPLICIT INTEGER,
  frames [2] SEQUENCE OF INTEGER
}

Circle ::= SEQUENCE
{
  point [1] IMPLICIT Point,
  radius [2] IMPLICIT IntUnit
}

Point ::= SEQUENCE
{
  latitude [1] IMPLICIT Coordinate,
  longitude [2] IMPLICIT Coordinate
}

Coordinate ::= InternationalString

AdditionalSemanticAttributes ::= SEQUENCE
{
  shortMeaning [1] IMPLICIT InternationalString OPTIONAL,
-- Short description of the attribute/element.
  unit [2] IMPLICIT Unit OPTIONAL,
-- Unit associated with the attribute/element.
  specificInstance [3] IMPLICIT InternationalString OPTIONAL,
-- specificInstance provides textual meanings for specific values of
-- the attribute/element.
  comment [4] IMPLICIT InternationalString OPTIONAL,
-- comment provides additional information about the attribute/ element.
  version [5] IMPLICIT InternationalString,
-- version provides the version of the attribute/ element.
  valueSyntax [6] IMPLICIT InternationalString
-- valueSyntax is the definition of the abstract data type used for
-- the attribute/element.
}

ChildrenResourceReport ::= CHOICE
{
  terminalCollection [1] IMPLICIT NULL,
  nonTerminalCollection [2] IMPLICIT ChildrenReports
}

ChildrenReports ::=SEQUENCE 
{
collectionId [1] IMPLICIT InternationalString,
collectionName [2] IMPLICIT InternationalString,
childReport [3] IMPLICIT ResourceReport
-- if the operation is a Search operation, {Z39.50-UserFormat-searchResult-1}
-- is selected for the EXTERNAL in ResourceReport.
-- Otherwise, {Z39.50-ResourceReport-resource-1} is selected
}

END


CIP24Order DEFINITIONS ::= BEGIN

IMPORTS OtherInformation, InternationalString, IntUnit FROM Z39-50-APDU-1995;

CIPOrder ::= CHOICE
{
  esRequest [1] IMPLICIT SEQUENCE{
  toKeep [1] OriginPartToKeep,
  notToKeep [2] OriginPartNotToKeep},
  taskPackage [2] IMPLICIT SEQUENCE{
  originPart [1] OriginPartToKeep,
  targetPart [2] TargetPart}
}

OriginPartToKeep ::= SEQUENCE
{
  action [1] IMPLICIT INTEGER {
  orderEstimate (1),
  orderQuoteAndSubmit (2),
  orderMonitor (3),
  orderCancel (4)},
  orderId [2] InternationalString OPTIONAL,
  orderSpecification [3] OrderSpecification OPTIONAL,
  statusUpdateOption [4] StatusUpdateOption OPTIONAL,
  userInformation [5] UserInformation OPTIONAL,
  otherInfo [6] OtherInformation OPTIONAL
}

OriginPartNotToKeep ::= SEQUENCE
{
  orderId [1] InternationalString OPTIONAL,
  orderSpecification [2] OrderSpecification OPTIONAL,
  userInformation [3] UserInformation OPTIONAL,
  otherInfo [4] OtherInformation OPTIONAL
}

TargetPart ::= SEQUENCE
{
  orderId [1] InternationalString,
  orderSpecification [2] OrderSpecification OPTIONAL,
  orderStatusInfo [3] OrderStatusInfo OPTIONAL,
  userInformation [4] UserInformation OPTIONAL,
  otherInfo [5] OtherInformation OPTIONAL
}

StatusUpdateOption ::= CHOICE
{
  manual [1] NULL,
  automatic [2] IMPLICIT INTEGER {
  eMail (1)}
}

UserInformation ::= SEQUENCE
{
  userId [1] InternationalString,
  userName [2] InternationalString OPTIONAL,
  userAddress [3] PostalAddress OPTIONAL,
  telNumber [4] InternationalString OPTIONAL,
  faxNumber [5] InternationalString OPTIONAL,
  emailAddress [6] InternationalString OPTIONAL,
  networkAddress [7] InternationalString OPTIONAL,
  billing [8] Billing OPTIONAL
}

OrderSpecification ::= SEQUENCE
{
  orderingCentreId [1] InternationalString,
  orderPrice [2] PriceInfo OPTIONAL,
  orderDeliveryDate [3] InternationalString OPTIONAL,
  orderCancellationDate [4] InternationalString OPTIONAL,
  deliveryUnits [5] SEQUENCE OF DeliveryUnitSpec,
-- RB 26/6/99 - needed to remove a "." from the end of the following line
  otherInfo [6] OtherInformation OPTIONAL
}

DeliveryUnitSpec ::= SEQUENCE
{
  deliveryUnitId [1] InternationalString OPTIONAL,
  deliveryUnitPrice [2] PriceInfo OPTIONAL,
  deliveryMethod [3] DeliveryMethod OPTIONAL,
  billing [4] Billing OPTIONAL,
  packages [5] SEQUENCE OF PackageSpec,
  otherInfo [6] OtherInformation OPTIONAL
}

DeliveryMethod ::= CHOICE
{
  eMail [1] InternationalString,
  ftp [2] FTPDelivery,
  mail [3] PostalAddress,
  otherInfo [4] OtherInformation
}

FTPDelivery ::= SEQUENCE
{
  transferDirection [1] IMPLICIT INTEGER
{
  push (0),
  pull (1)
},
  ftpAddress [2] InternationalString
}

Billing ::= SEQUENCE
{
  paymentMethod [1] PaymentMethod,
  customerReference [2] IMPLICIT CustomerReference,
  customerPONumber [3] IMPLICIT InternationalString OPTIONAL
}

PaymentMethod ::= CHOICE
{
  billInvoice [0] IMPLICIT NULL,
  prepay [1] IMPLICIT NULL,
  depositAccount [2] IMPLICIT NULL,
  privateKnown [3] IMPLICIT NULL,
-- RB 26/6/99 - needed to remove a ","  and a "}"
-- from the end of the following line
  privateNotKnown [4] IMPLICIT EXTERNAL
}

CustomerReference ::= SEQUENCE
{
  customerId [1] InternationalString,
  accounts [2] SEQUENCE OF InternationalString
}

PostalAddress ::= SEQUENCE
{
  streetAddress [1] InternationalString,
  city [2] InternationalString,
  state [3] InternationalString,
  postalCode [4] InternationalString,
  country [5] InternationalString
}

PackageSpec ::= SEQUENCE
{
  packageId [1] InternationalString OPTIONAL,
  packagePrice [2] PriceInfo OPTIONAL,
  package [3] CHOICE
  {
    predefinedPackage [1] PredefinedPackage,
    adHocPackage [2] AdHocPackage
  },
  packageMedium [4] InternationalString,
  packageKByteSize [5] INTEGER,
  otherInfo [6] OtherInformation OPTIONAL
}

PredefinedPackage ::= SEQUENCE
{
  collectionId [1] InternationalString,
  orderItems [2] SEQUENCE OF OrderItem,
  otherInfo [3] OtherInformation OPTIONAL
}

AdHocPackage ::= SEQUENCE OF OrderItem

OrderItem ::= SEQUENCE
{
  productId [1] InternationalString,
  productPrice [2] PriceInfo OPTIONAL,
  productDeliveryOptions [3] ProductDeliveryOptions OPTIONAL,
  processingOptions [5] ProcessingOptions OPTIONAL,
  sceneSelectionOptions [6] SceneSelectionOptions OPTIONAL,
  orderStatusInfo [7] OrderStatusInfo OPTIONAL,
-- RB 26/6/99 - needed to remove a "." from the end of the following line
  otherInfo [8] OtherInformation OPTIONAL
}

ProductDeliveryOptions::= SEQUENCE
{
  productByteSize [1] INTEGER OPTIONAL,
  productFormat [2] InternationalString OPTIONAL,
  productCompression [3] InternationalString OPTIONAL,
  otherInfo [4] OtherInformation OPTIONAL
}

ProcessingOptions ::= CHOICE
{
  formattedProcessingOptions [1] EXTERNAL,
  unformattedProcessingOptions [2] InternationalString
}

SceneSelectionOptions ::= CHOICE
{
  formattedSceneSelectionOptions [1] EXTERNAL,
  unformattedSceneSelectionOptions [2] InternationalString
}

PriceInfo ::= SEQUENCE
{
  price [1] IntUnit,
  priceExpirationDate [2] InternationalString,
  additionalPriceInfo [3] InternationalString OPTIONAL
}

OrderStatusInfo ::= SEQUENCE
{
  orderState [1] CHOICE
  {
    staticState [1] StaticState,
    dynamicState [2] DynamicState
  },
  additionalStatusInfo[2] InternationalString OPTIONAL
}

StaticState ::= [1] IMPLICIT INTEGER
{
  orderNotValid (1),
  orderEstimated (2),
  orderCompleted (3)
}

DynamicState ::= [2] IMPLICIT INTEGER
{
  orderBeingEstimated (4),
  orderBeingQuoted (5),
  orderBeingProcessed (6),
  orderBeingCancelled (7),
  orderBeingDeleted (8)
}


FormattedProductProcessingOptions ::= SEQUENCE OF ProcessingOptionSelection

ProcessingOptionSelection ::= SEQUENCE
{
  processingOptionName [1] InternationalString,
  processingOptionSelectedValues [2] SEQUENCE OF ProcessingOptionValue
}

ProcessingOptionValue ::= CHOICE
{
  numericProcessingOptionValue [1] InternationalString,
  stringProcessingOptionValue [2] InternationalString
}


FormattedSceneSelectionOptions ::= SEQUENCE
{
  sceneType [1] InternationalString ,
  horizontalSelection [2] HorizontalSelection OPTIONAL,
  verticalSelection [3] VerticalSelection OPTIONAL,
  temporalSelection [4] TemporalSelection OPTIONAL
}

HorizontalSelection ::= CHOICE
{
  rectangleSceneSelection [1] RectangleSceneSelection,
  boundingRectangleSelection [2] BoundingRectangleSelection,
  polygonSelection [3] PolygonSelection,
  circleSelection [4] CircleSelection
}

RectangleSceneSelection ::= SEQUENCE
{
  acrossGrid [1] INTEGER,
  alongGridUnitType [2] IMPLICIT INTEGER {
  relative (0),
  timeBased (1)},
  alongGrid [3] INTEGER,
  acrossSize [4] INTEGER,
  alongSize [5] INTEGER,
  acrossCenter [6] INTEGER,
  alongCenter [7] INTEGER
}

BoundingRectangleSelection ::= SEQUENCE
{
-- RB 26/6/99 the following 4 lines are modified so that
-- the definitions start with lower case letters
  westBoundingCoordinate [1] IMPLICIT Coordinate,
  eastBoundingCoordinate [2] IMPLICIT Coordinate,
  northBoundingCoordinate [3] IMPLICIT Coordinate,
  southBoundingCoordinate [4] IMPLICIT Coordinate
}

PolygonSelection ::= SEQUENCE
{
  polygonProjection [1] MapProjection OPTIONAL,
  gPolygonOuterRing [2] SEQUENCE OF Point
}

-- RB 26/6/99 the following line had the word IMPLICIT removed
MapProjection ::= InternationalString

CircleSelection ::= SEQUENCE
{
  center [1] Point,
  radiusValue [2] IMPLICIT IntUnit
}

Point ::= SEQUENCE
{
-- RB 26/6/99 the following 2 lines are modified so that
-- the definitions start with lower case letters
  latitude [1] IMPLICIT Coordinate,
  longitude [2] IMPLICIT Coordinate
}

Coordinate ::= InternationalString

VerticalSelection ::= SEQUENCE
{
  lowAltitude [1] IMPLICIT InternationalString,
  highAltitude [2] IMPLICIT InternationalString
}

TemporalSelection ::= SEQUENCE
{
  startDate [1] Time,
  endDate [2] Time
}


Time ::= InternationalString

END
